# tile_tele_req_analysis

## #1: Valid Voltage (Functional)
The operating voltage range should be between 10 to 20 V.

## #6: Debounce Logic (Functional)
This is the most important part of the whole model development as it depicts the main working flow of switch and is in with ECU working coordinations. This logic flowchart can be modelled in Simulink with the help of State-flow.
Once the ignition is ON then the ECU should ensure all the switches are in the unstuck position
Stuck is a hardware issue, this will block the desired signal being executed. There are chances for the execution of faulty signals during this stuck position. In order to avoid these errors debounce time is being introduced. This will avoid/fix all the input errors and the actual signal will be processed.

## #10: Enabled System Requirements (Functional)
The system to be enabled the valid voltage and as well as the configuration parameters has to be True.
The configuration parameters like the voltage drop, ignition status On.
